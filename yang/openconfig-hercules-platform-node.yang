submodule openconfig-hercules-platform-node {

  yang-version "1";

  belongs-to openconfig-hercules-platform {
    prefix "herc-platform";
  }

  // import some basic types
  import openconfig-platform { prefix oc-platform; }
  import openconfig-extensions { prefix oc-ext; }

  // meta
  organization
    "OpenConfig Hercules Working Group";

  contact
    "openconfig-hercules@googlegroups.com";

  description
    "This submodule defines schema extensions to the
    OpenConfig platform model for a switching node component
    in the Hercules switch profile.";

  oc-ext:openconfig-version "0.2.0";

  revision 2018-06-01 {
    description
      "Initial version.";
    reference "0.2.0";
  }


  // identity statements

  // typedef statements

  // grouping statements

  grouping node-config {
    description
      "Configuration data for switching nodes.";

    leaf node-id {
      type uint64;
      description
        "The numeric id used by the controller to address the node.

        Each node (i.e., switching ASIC) is addressed by the
        controller or configuration manager based on its numeric
        identifier (which can be assigned through configuration).  In
        order to effectively manage port availability, for example, it
        is important for the controller to understand which ports are
        managed by which nodes.";
  
    }

  }

  grouping node-vendor-data-top {
    description
      "Configuration data for vendor ASICs";

    container vendor-data {
      description
        "This is an anchor container for defining augmentations that
        "add ASIC-specific data to the model.";

      container config {
        description
          "Vendor-specific configuration data for a node.";
      }

      container state {
        config false;
        description
          "Vendor-specific operational state data for a node.";
      }
    }
  }


  // data definition statements

  // augment statements
  augment "/oc-platform:components/oc-platform:component/" +
          "oc-platform:integrated-circuit/oc-platform:config" {
    description
      "Configuration data for nodes";

    uses node-config;
  }

  augment "/oc-platform:components/oc-platform:component/" +
          "oc-platform:integrated-circuit/oc-platform:state" {
    description
      "Operational state data for nodes";

    uses node-config;
  }

  augment "/oc-platform:components/oc-platform:component/" +
          "oc-platform:integrated-circuit" {
    description
      "Anchor container for vendor-specific data";

    uses node-vendor-data-top;
  }

  // rpc statements

  // notification statements

}
